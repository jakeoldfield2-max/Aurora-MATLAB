# Aurora_Requirements

## MRD-MIS-001: The launch vehicle should reach an apogee of 2200ft. (Functional)
- Keywords: Verification: A, Notes: Marks are given based on the apogee reached. 100% of the marks are achieved if an apogee of exactly 2200ft is reached.

## MRD-MIS-002: The launch vehicle shall not fly above 3000ft without a dual deployment recovery system. (Functional)
If a rocket exceeds an apogee of 3000ft, they are required to incorporate a dual-deployment recovery system according to Midlands Rocketry Club Rules.
- Rationale: Any launch vehicle which passes the 3000ft altitude line must be equipped with a dual-deployment recovery system as per the rules of the site. This is for safety reasons and cannot be disregarded.
- Keywords: Verification: A, Notes: Since the goal is to reach an apogee of 2500ft, passing an apogee of 3000ft will result in heavy penalisations and deduction of points.

## MRD-MIS-003: The launch vehicle shall not fly above the Midlands Rocketry Club's NOTAM limit. (Functional)
The Competition's launch site is overseen by the Midlands Rocketry Club, which can only secure a maximum altitude of 3500ft on the day. Rockets MUST NOT exceed this altitude.
- Rationale: Launch vehicles travelling higher than 3500 pose a serious risk to low-flying aircraft and violate the MRC's agreement with the UK Civil Aviation Authority.
- Keywords: Verification: A, Notes: Any rockets which pass a maximum altitude of 3500ft will be automatically given 0 marks, and will be heavily penalised.

## MRD-MIS-004: The launch vehicle shall be powered by a 2-grain 29mm G-class ammonium perchlorate solid rocket motor with a total impulse under 130Ns. (Functional)
Competition restrictions dictate that only certain approved motors can be used in the NRC. Self-made motors are not allowed. Cesaroni and AeroTech motors are standard on the UK Market, and have been approved by UKSEDS for competition use.
- Rationale: Teams are provided with these G-Class motors because they are classified as mid-power motors and do not require UKRA certification to purchase or fly.
- Keywords: Verification: D, Notes: These motors have a total impulse under 130Ns. Be mindful of this when designing the rocket.

## MRD-MIS-005: The rocket motor shall be supplied by Cesaroni Technology Inc. or AeroTech. (Functional)
Due to safety and competition restrictions, only approved motors can be used in NRC. UKSEDS will not allow self-made motors or motors from unlicensed manufacturers.
- Rationale: Motors from Cesaroni and AeroTech are UKSEDS verified and approved, and have been allowed for competition use.
- Keywords: Verification: D

## MRD-MIS-006: The rocket motor shall be obtained through UKSED's NRC Organising team. (Functional)
Significant issues have arisen in previous years with communication between teams and motor suppliers. The NRC organising team are the only group communicating with motor suppliers about motor orders. This ensures all motors are handled correctly by qualified persons.
- Rationale: NRC Organising teams communicating directly with reliable motor providers results in less confusion and issues with motor sourcing. By obtaining motors through the UKSEDS' NRC Organising team, the motors will be handled correctly and will be safe for use.
- Keywords: Verification: D

## MRD-MIS-007: The launch vehicle shall carry a rideshare payload with a minimum weight of 100g. (Functional)
The rideshare payload will be provided by teams, and they are able to decide what it will be.
- Rationale: N/A
- Keywords: Verification: D, Notes: The rideshare payload will need to provide power to "The Customer's" payload. The requirements given elsewhere should provide more information on what this payload should include.

## MRD-MIS-008: The launch vehicle shall land no further than 750m from the launch pad under a windspeed of 10m/s during descent. (Functional)
Private properties near the NRC Launch site.
- Keywords: Verification: A

## MRD-CPD-001: The launch vehicle shall provide a DC bus voltage of 3.5-5Volts to "The Customer's" payload. (Functional)
N/A
- Rationale: N/A
- Keywords: Verification: D,T, Notes: The rideshare payload will need to be the component which provides the necessary voltage.

## MRD-CPD-002: The launch vehicle shall provide power to "The Customer's" payload for a minimum of 45 minutes. (Functional)
This 45 minute window includes time on the pad, flight and recovery. This assumes the rocket will be on the pad for 15 minutes.
- Rationale: The Customer's payload will need power before and after flight. As such, it is appropriate to assume 45 minutes of power will suffice.
- Keywords: Verification: D

## MRD-CPD-003: The launch vehicle shall provide sufficient current to power "The Customer's" payload. (Functional)
N/A
- Rationale: If insufficient current is provided, "The Customer's" payload will be unable to carry out its function.
- Keywords: Verification: D,T

## MRD-CPD-004: The launch vehicle shall provide power via a female XT30 connector at the top and bottom of "The Customer's" payload. (Functional)
The payload only needs to be powered via the top or bottom port. Two options have been given to provide the participants with design flexibility.
- Rationale: The payload will have a male XT30 connector, so the team will need to provide a female connector.
- Keywords: Verification: D, Notes: See the photos under NRC CAD tab for a visual representation.

## MRD-CPD-005: The launch services provider shall provide a microSD with a minimum of 16GB of storage for "The Customer's" payload. (Functional)
N/A
- Rationale: SD Card needed to record flight data.
- Keywords: Verification: D

## MRD-CPD-006: The launch vehicle shall mechanically interface with "The Customer's" payload via the launch vehicle's adapter. (Functional)
The launch vehicle adapter file will be shared with teams through the documentation page on the website. The team is expected to print this adapter and provide it. Having an NRC organiser distributed design would reduce interface issues on launch day.
- Rationale: The Customer's payload needs to interface with the launch vehicle to remain secure throughout flight.
- Keywords: Verification: D,T, Notes: Teams can modify the launch vehicle adapter to interface with the rocket design, but the face which meets with the payload should remain untouched.

## MRD-CPD-007: The launch vehicle shall provide a minimum payload bay of 40mm in diameter and 53mm in length for "The Customer's" payload (not including the launch vehicle adapter). (Functional)
Teams should design a payload bay to have a small amount of extra space to account for any tolerancing issues. Print out a copy of the dummy "Customer's" payload to carry out checks and determine an assembly procedure before competition day.
- Keywords: Verification: D, Notes: Checking that the payload bay will meet these requirements is vital to the success of the launch. This should be tested and checked thoroughly before launch day.

## MRD-CPD-008: The thrust vector of the launch vehicle shall go through the centre of "The Customer's" payload. (Functional)
See the NRC CAD tab for a visual diagram.
- Rationale: N/A
- Keywords: Verification: D

## MRD-CPD-009: The launch vehicle shall provide permanent external access to the following points for "The Customer's" payload. (See the points circled in RED in the NRC CAD tab) (Functional)
N/A
- Rationale: The camera hole and screw switch hole should be accessible from the outside of the rocket.
- Keywords: Verification: D

## MRD-CPD-010: The launch vehicle payload bay shall be unpressurised. (Functional)
The payload bay should be unpressurised to ensure "The Customer's" payload can determine the altitude of the launch vehicle.
- Rationale: Unpressurised to allow altitude recordings.
- Keywords: Verification: D

## MRD-CPD-011: Teams shall provide their own bolts to mount "The Customer's" payload into the vehicle launch adapter. (Functional)
Bolts are needed to "mate" the payload adapter and the payload to each other. 3 M3 bolts are required as standard; however, teams are advised to bring spares in a variety of lengths.
- Rationale: Teams will modify the launch vehicle adapter, so will need their own bolts of varying lengths.
- Keywords: Verification: D, Notes: UKSEDS will have a small amount of spare M3 bolts in various sizes.

## MRD-RPD-001: The rideshare payload shall contain a printed circuit board designed from scratch. (Functional)
This PCB should be designed fresh for this year's competition. Training courses will be sent to teams in due course throughout the year.
- Rationale: A new PCB should be designed by the teams to ensure fairness.
- Keywords: Verification: D

## MRD-RPD-002: The rideshare payload shall detect the launch vehicle's altitude. (Functional)
IMU's have a tendency to drift quickly with time, leading to inaccurate results. Hence, barometers should be used instea
- Rationale: N/A
- Keywords: Verification: D

## MRD-RPD-003: The rideshare payload shall be able to produce an altitude vs. time plot in feet per second within 10 minutes of launch vehicle recovery. (Functional)
The payload does not have to have a screen to show the graph, and an external screen, like a laptop, may be used to accomplish this.
- Rationale: N/A
- Keywords: Verification: D

## MRD-RPD-004: The rideshare payload shall be able to provide an apogee value in feet within 10 minutes of recovery without the use of external equipment. (Functional)
Tools can be used to gain access to the rideshare payload, but equipment like laptops cannot be used to retrieve apogee data from the rideshare payload.
- Rationale: N/A
- Keywords: Verification: D

## MRD-RPD-005: The rideshare payload shall have a silkscreen on the printed circuit board containing the team logo. (Functional)
N/A
- Rationale: N/A
- Keywords: Verification: D

## MRD-RPD-006: The rideshare payload should record at least one extra type of data and present this within 10 minutes of recovery. (Functional)
External equipment may be used to display this data. The data must not be collected with the same sensor used for MRD-RPD-002.
- Rationale: N/A
- Keywords: Verification: D

## TSN-MOR-001: Mounting of the motor in the rocket. (Functional)
The rocket motor/motor case shall be clamped axially at both ends.
- Rationale: The motor must be securely mounted in the launch vehicle, or it could break free and pose a safety risk.
- Keywords: Verification: D, Notes: Single-use or reload motors are the only 2 types of motors allowed under NRC rules. Since single-use motors do not have a case, they should be directly clamped to the launch vehicle. Reload motors need a case, and this case should be clamped to the launch vehicle. The mount used must transmit thrust loads from the motor to the structure of the rocket, and the motor must not slip out during handling or flight.

## TSN-MOR-002: Motor Mount Strength Requirements (Functional)
The rocket motor mount shall be designed to withstand a force equivalent to twice the maximum motor thrust without permanent deformation.
- Rationale: Designing the mount to tolerate thrust forces above what is expected will result in a reliable mount which will not fail during launch or flight.
- Keywords: Verification: T

## TSN-MOR-003: Motor Mount Strength Requirements (Functional)
The rocket motor shall be designed to withstand a lateral force in any direction equal to a thrust misalignment of 5 degrees at the maximum motor thrust cantilevered about the vehicle's centre of gravity.
- Rationale: If the motor mount is unable to withstand all thrust loads (both axial and lateral), then the mount may critically fail, resulting in loss of the launch vehicle and a potential safety hazard.
- Keywords: Verification: T

## TSN-SMN-001: The rocket shall have a minimum velocity of 20m/s when leaving the launch rail. (Functional)
The launch rail at Midlands rocketry club will be approximately 2 metres.
- Keywords: Verification: A

## TSN-SMN-003: The rocket shall have a stability margin between 1.75 and 2.5 diameters during all phases of flight before apogee. (Functional)
The static stability margin is the distance between the centre of mass and the centre of pressure.
- Rationale: This is the static stability margin, which means the rocket is not in flight.
- Keywords: Verification: A

## TSN-SAR-001: Fin Alignment (Functional)
The geometric alignment of each fin shall be within 2 degrees of the projected longitudinal axes of symmetry of the rocket.
- Keywords: Verification: I

## TSN-SAR-002: Fin Longitudinal Loading (Functional)
Each fin must be able to support a suspended load from its tip equal to twice the fin mass times the rocket's maximum axial acceleration during any flight phase.
- Keywords: Verification: T

## TSN-SAR-003: Fin Lateral Loading (Functional)
Each fin shall withstand a transverse load equal to the rocket's launch mass when suspended from the fin tip with a maximum lateral deflection of less than 10 degrees in either rotational direction.
- Keywords: Verification: T

## TSN-SAR-004: Fuselage Stiffness (Functional)
The launch-ready rocket shall deflect less than 10mm per metre length in any lateral direction when suspended from it's centre of mass.
- Keywords: Verification: T

## TSN-SAR-005: Fuselage Stiffness (Functional)
The mating length between a coupler and body tube shall be a minimum of 1 body tube diameter when using plastics or composites.
- Rationale: When rockets are coupled together using several tubes, the way the tubes are joined can often lead to unsatisfactory levels of stiffness. To prevent this flexing along the rocket body, the minimum mating length should be 1 body tube diameter.
- Keywords: Verification: D, Notes: If sliding connections are used, the minimum mating length between a coupler and tube should always be 1 diameter. Additionally, the fit between parts must stop any noticeable rotation at the joint.

## TSN-SAR-006: Static Strength Requirements (Functional)
All structural parts used shall withstand twice their expected maximum inertial and aerodynamic loads without failure.
- Keywords: Verification: T, Notes: If teams wish to re-use a launch vehicle, all parts must withstand 1.5x applied loads without permanent deformation.

## TSN-SAR-007: Launch Lug (Functional)
All rockets shall be equipped with a minimum of 2 rail buttons.
- Rationale: At the Midlands Rocketry Club, teams usually fly on 2m rails, which are compatible with 6mm launch buttons.
- Keywords: Verification: D, Notes: NRC recommends that delrin rail buttons are used.

## TSN-SAR-008: Finite Element Analysis (Functional)
Finite Element Analysis (FEA) shall not be used to produce evidence for any structural requirements.
- Rationale: Incorrect assumptions are often made using FEA, leading to previous issues in flight readiness review, where designs cannot pass real-world structural tests.
- Keywords: Verification: D, Notes: Teams are encouraged to learn FEA for NRC, and are welcome to use it in competition reports and documentation as supplementary evidence. It cannot be used, due to safety reasons, for verifying structural requirements.

## TSN-ESS-001: Internal Power Supply (Functional)
The rocket shall be capable of being switched on and left to run using its internal power source for a minimum of 15 minutes on the launch pad.
- Rationale: Energy is needed for "The Customer's" payload to carry out it's functions. As such, at least 15 minutes of power is needed on the launch pad.
- Keywords: Verification: A, Notes: Teams should ideally have a way to arm the rocket externally, so it can be armed on the launch pad. If this is not possible, it will need to be powered on for much longer (up to 1 hour) on the launch day before being placed on the pad.

## TSN-ESS-002: Internal Power Supply (Functional)
The rocket shall be capable of being armed within 5 minutes at the launch site.
- Rationale: Many delays on competition days are caused by teams having to fully disassemble their rockets to arm them or switch on a payload. A rocket which can be quickly armed will reduce delays on the day and help the competition to run smoothly.
- Keywords: Verification: D, Notes: It is highly advisable for rockets to be armed externally using a pull pin or screw switch.

## TSN-ESS-003: Electrical Considerations (Functional)
The rocket shall not contain single-core wire.
- Rationale: Single-core wire is considered too fragile to be used as the electrical cable for primary systems. Multi-core wire is tougher and more reliable.
- Keywords: Verification: D, Notes: During assembly, testing and flight, electronic circuits and wiring will be subjected to high levels of abuse. Hence, construction should be rugged and to a high standard of workmanship. Teams should be careful when using electromechanical components, and ensure that the components can withstand high acceleration and vibration loads. Switches should be placed in the correct orientation, as they can only withstand high G loads along certain axes. Recovery system deployment shock loads are an important factor to consider because they can exceed thrust loads.

## TSN-ESS-004: Radio Frequencies (Functional)
Teams shall conform to Ofcom's IR 2030 radio frequency regulations.
- Rationale: Ofcom limits the type of radio frequencies which can be used recreationally.
- Keywords: Verification: D, Notes: See Ofcom's IR 2030 document (latest version) to ensure they are complying with regulations. 868MHz and 433MHz are the 2 most popular choices.

## TSN-RRS-001: Use of Recovery System (Functional)
The rocket shall have a recovery system.
- Rationale: All rockets must have a system to recover them in a safe and controlled fashion. This can be accomplished using a parachute, which is deployed when a rocket reaches apogee.
- Keywords: Verification: D

## TSN-RRS-002: Landing Speeds (Functional)
The recovery system shall reduce the rocket's vertical landing speed to less than 15m/s.
- Rationale: This can be demonstrated using Open Rocket simulations if using a parachute based recovery system. If an alternative system is used, then its effectiveness should be demonstrated with hand calculations and a possible real-world test.
- Keywords: Verification: A

## TSN-RRS-003: Maximum Post-Apogee Range (Functional)
After reaching apogee, the rocket shall not drift more than 1 kilometre before landing at wind speeds of 15m/s.
- Rationale: Rockets need to land inside the landowner's boundaries; hence a 1km radius shall be used.
- Keywords: Verification: A, Notes: The prospective launch site is quite windy, but all rockets must still land within the boundaries. It is recommended to make the recovery device highly visible to assist recovery.

## TSN-RRS-004: Flight Computer (Functional)
If a flight computer is used for recovery, it shall be a COTS or UKRA qualified system.
- Rationale: The purpose of a flight computer is to activate the recovery system when the rocket reaches apogee. COTS means 'commercial-off-the-shelf'. This means teams cannot design an in-house recovery computer to operate on its own.
- Keywords: Verification: D, Notes: Teams are allowed to use an SRAD (student-researched-and-developed) flight computer that has been flight qualified to UKRA's standards. Teams can develop their own recovery circuits, but as per UKRA safety code section 2, this will mean the rocket is classed as experimental, and so UKRA section 8 applies. This means that SRAD recovery electronics must be flown as backup to a COTS recovery system until they have been qualified.

## TSN-RRS-005: Isolation of Recovery Circuit (Functional)
Any electronic recovery circuits should be electrically isolated from other electronic systems.
- Keywords: Verification: D, Notes: It is recommended that all of the recovery sequencing circuitry be electrically isolated (including batteries) from any other circuit in the rocket.

## TSN-RRS-006: Detection of Apogee (Functional)
Tilt Switches shall not be used.
- Rationale: Inaccuracy in tilt switches means they are not viable detectors.
- Keywords: Verification: D, Notes: Detectors relying on the physical orientation of the rocket relative to gravity vector to detect apogee are inaccurate and shouldn't be used.

## TSN-RRS-007: Flight Computer Disarming System (Functional)
Any flight computers used to trigger recovery systems shall have an externally accessible disarming mechanism.
- Rationale: The flight computer (if used) must have a safe disarming mechanism to prevent inadvertent activation of the recovery system during handling and loading. Otherwise, pyrotechnic actuators could go off and cause damage.
- Keywords: Verification: D, Notes: The system must be kept in a disarmed (safe) condition until the rocket is safely loaded onto the launch pad.

## TSN-RRS-008: Transmission of Recovery Shock Loads (Functional)
Recovery loads shall be transmitted via eye bolts through bulkheads with a nut on the other side.
- Keywords: Verification: D, Notes: The main recovery shock loads must not be transmitted in shear through screw threads into the rocket body.

## TSN-RRS-009: Shock Cord (Functional)
Recovery systems which use shock cords shall have a minimum length of 2m.
- Rationale: Enough length of cord is needed to safely dissipate energy released during airframe seperation.
- Keywords: Verification: D, Notes: Since a lot of energy is released when an ejection charge goes off, the shock cords used need to be a sufficient length to prevent shock cord snapping.

## TSN-RRS-010: Shock Cord (Functional)
Any shock cords shall be made of kevlar.
- Rationale: A cheap and strong material.
- Keywords: Verification: D, Notes: Relatively inexpensive compared to alternative cords.

## TSN-ARY-001: Alternative Recovery Definition (Functional)
All rockets must conform to CAA UAS laws.
- Keywords: Verification: D, Notes: See Civil Aviation Authority documentation regarding this.

## TSN-ARY-002: Alternative Recovery Definition (Functional)
All rockets must conform to UKRA safety code.
- Keywords: Verification: D, Notes: Model Rocket Safety Code – UKRA

## TSN-ARY-003: Active Stabilisation and Recovery (Functional)
Active stabilisation shall only be used on ascent.
- Keywords: Verification: D, Notes: As per UKRA's safety code, active stabilisation can only be used on ascent. Active recovery must only be used to guide the rocket back to the launch site on descent.
